# -*- coding: utf-8 -*-

# Macro Begin: /Users/akashlevy/OneDrive - Levylab/Documents/Research/NEM-Relay-CAD/FEM-spring-const.FCMacro +++++++++++++++++++++++++++++++++++++++++++++++++
import FreeCAD
import Part
import Fem
import FemGui
import ObjectsFem

#### Begin command Part_ShapeFromMesh
name = Gui.Selection.getSelection()[0].Name
App.ActiveDocument.addObject("Part::Feature","relay001")
__shape__=Part.Shape()
__shape__.makeShapeFromMesh(App.ActiveDocument.getObject(name).Mesh.Topology,0.1)
App.ActiveDocument.getObject("relay001").Shape=__shape__
App.ActiveDocument.getObject("relay001").purgeTouched()
del __shape__
#### End command Part_ShapeFromMesh

#### Begin command Part_RefineShape
__shape = Part.getShape(App.ActiveDocument.getObject('relay001'),'',needSubElement=False,refine=True)
App.ActiveDocument.addObject('Part::Feature','relay001').Shape=__shape
App.ActiveDocument.recompute()
#### End command Part_RefineShape

#### Begin command Part_MakeSolid
__s__=App.ActiveDocument.relay001001.Shape
__s__=Part.Solid(__s__)
__o__=App.ActiveDocument.addObject("Part::Feature","relay001001_solid")
__o__.Label="relay001001 (Solid)"
__o__.Shape=__s__
del __s__, __o__
#### End command Part_MakeSolid

#### Begin command FEM_Analysis
ObjectsFem.makeAnalysis(FreeCAD.ActiveDocument, 'Analysis')
FemGui.setActiveAnalysis(FreeCAD.ActiveDocument.ActiveObject)
ObjectsFem.makeSolverCalculixCcxTools(FreeCAD.ActiveDocument)
FemGui.getActiveAnalysis().addObject(FreeCAD.ActiveDocument.ActiveObject)
#### End command FEM_Analysis

#### Begin command FEM_MaterialSolid
FemGui.getActiveAnalysis().addObject(ObjectsFem.makeMaterialSolid(FreeCAD.ActiveDocument))
App.ActiveDocument.getObject("MechanicalSolidMaterial").Material = { "AuthorAndLicense":"Poly-SiGe-0.4", "CardName":"Poly-SiGe-0.4", "Density":"4126 kg/m^3", "Name":"Poly-SiGe (x=0.4)", "PoissonRatio":"0", "ShearModulus":"57.00 GPa", "YoungsModulus":"145 GPa" }
#### End command FEM_MaterialSolid

#### Begin command FEM_MeshNetgenFromShape
ObjectsFem.makeMeshNetgen(FreeCAD.ActiveDocument, 'FEMMeshNetgen')
FreeCAD.ActiveDocument.ActiveObject.Shape = FreeCAD.ActiveDocument.relay001001_solid
FemGui.getActiveAnalysis().addObject(FreeCAD.ActiveDocument.ActiveObject)
App.ActiveDocument.getObject("FEMMeshNetgen").Fineness = u"VeryCoarse"
App.ActiveDocument.recompute()
#### End command FEM_MeshNetgenFromShape

#### Begin command FEM_ConstraintFixed
App.activeDocument().addObject("Fem::ConstraintFixed","ConstraintFixed")
App.activeDocument().ConstraintFixed.Scale = 1
App.activeDocument().Analysis.addObject(App.activeDocument().ConstraintFixed)
for amesh in App.activeDocument().Objects:
    if "ConstraintFixed" == amesh.Name:
        amesh.ViewObject.Visibility = True
    elif "Mesh" in amesh.TypeId:
        aparttoshow = amesh.Name.replace("_Mesh","")
        for apart in App.activeDocument().Objects:
            if aparttoshow == apart.Name:
                apart.ViewObject.Visibility = True
        amesh.ViewObject.Visibility = False
App.ActiveDocument.ConstraintFixed.References = [(App.ActiveDocument.relay001001_solid,"Face35"), (App.ActiveDocument.relay001001_solid,"Face23"), (App.ActiveDocument.relay001001_solid,"Face21"), (App.ActiveDocument.relay001001_solid,"Face32"), (App.ActiveDocument.relay001001_solid,"Face44"), (App.ActiveDocument.relay001001_solid,"Face42"), (App.ActiveDocument.relay001001_solid,"Face10"), (App.ActiveDocument.relay001001_solid,"Face9"), (App.ActiveDocument.relay001001_solid,"Face22"), (App.ActiveDocument.relay001001_solid,"Face24"), (App.ActiveDocument.relay001001_solid,"Face33"), (App.ActiveDocument.relay001001_solid,"Face34"), (App.ActiveDocument.relay001001_solid,"Face43"), (App.ActiveDocument.relay001001_solid,"Face41"), (App.ActiveDocument.relay001001_solid,"Face11"), (App.ActiveDocument.relay001001_solid,"Face8")]
#App.ActiveDocument.ConstraintFixed.References = [(App.ActiveDocument.relay001001_solid,"Face34"), (App.ActiveDocument.relay001001_solid,"Face25"), (App.ActiveDocument.relay001001_solid,"Face26"), (App.ActiveDocument.relay001001_solid,"Face23"), (App.ActiveDocument.relay001001_solid,"Face9"), (App.ActiveDocument.relay001001_solid,"Face11"), (App.ActiveDocument.relay001001_solid,"Face36"), (App.ActiveDocument.relay001001_solid,"Face13"), (App.ActiveDocument.relay001001_solid,"Face10"), (App.ActiveDocument.relay001001_solid,"Face24"), (App.ActiveDocument.relay001001_solid,"Face8"), (App.ActiveDocument.relay001001_solid,"Face12"), (App.ActiveDocument.relay001001_solid,"Face35"), (App.ActiveDocument.relay001001_solid,"Face37"), (App.ActiveDocument.relay001001_solid,"Face43"), (App.ActiveDocument.relay001001_solid,"Face44")]
App.ActiveDocument.recompute()
#### End command FEM_ConstraintFixed

#### Begin command FEM_ConstraintForce
App.activeDocument().addObject("Fem::ConstraintForce","ConstraintForce")
App.activeDocument().Analysis.addObject(App.activeDocument().ConstraintForce)
for amesh in App.activeDocument().Objects:
    if "ConstraintForce" == amesh.Name:
        amesh.ViewObject.Visibility = True
    elif "Mesh" in amesh.TypeId:
        aparttoshow = amesh.Name.replace("_Mesh","")
        for apart in App.activeDocument().Objects:
            if aparttoshow == apart.Name:
                apart.ViewObject.Visibility = True
        amesh.ViewObject.Visibility = False
App.ActiveDocument.ConstraintForce.Force = 1
App.ActiveDocument.ConstraintForce.Direction = None
App.ActiveDocument.ConstraintForce.Reversed = True
App.ActiveDocument.ConstraintForce.Scale = 1
App.getDocument('Unnamed').ConstraintForce.setExpression('Force', u'1e-07')
App.ActiveDocument.ConstraintForce.References = [(App.ActiveDocument.relay001001_solid,"Face1")]
App.ActiveDocument.recompute()
#### End command FEM_ConstraintForce

#### Begin command ToggleVisibility
Gui.Selection.clearSelection()
Gui.Selection.addSelection('Unnamed','FEMMeshNetgen')
Gui.Selection.addSelection('Unnamed','relay001')
Gui.Selection.addSelection('Unnamed','relay001001')
Gui.Selection.addSelection('Unnamed','ConstraintFixed')
Gui.Selection.addSelection('Unnamed','ConstraintForce')
Gui.runCommand('Std_ToggleVisibility',0)

Gui.Selection.clearSelection()
Gui.Selection.addSelection('Unnamed','relay001001_solid')
Gui.runCommand('Std_ToggleVisibility',1)
#### End command ToggleVisibility

#### Begin command ViewZoomToFit
Gui.SendMsgToActiveView("ViewFit")
#### End command ViewZoomToFit

#### Begin command ViewIsometricCmd
Gui.activeDocument().activeView().viewIsometric()
#### End command ViewIsometricCmd

#### Begin command ToggleVisibility
Gui.Selection.clearSelection()
Gui.Selection.addSelection('Unnamed','ConstraintForce')
Gui.runCommand('Std_ToggleVisibility',1)
#### End command ToggleVisibility

# Macro End: /Users/akashlevy/OneDrive - Levylab/Documents/Research/NEM-Relay-CAD/FEM-spring-const.FCMacro +++++++++++++++++++++++++++++++++++++++++++++++++
